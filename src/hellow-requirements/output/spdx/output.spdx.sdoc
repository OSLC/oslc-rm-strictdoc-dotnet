[DOCUMENT]
TITLE: Requirements for Untitled Project
OPTIONS:
  VIEW_STYLE: Inline

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: SPDX_DOCUMENT
  FIELDS:
  - TITLE: UID
    TYPE: String
    REQUIRED: True
  - TITLE: SPDXID
    TYPE: String
    REQUIRED: True
  - TITLE: TITLE
    TYPE: String
    REQUIRED: False
  - TITLE: STATEMENT
    TYPE: String
    REQUIRED: False
  RELATIONS:
  - TYPE: Child
    ROLE: CONTAINS
- TAG: SPDX_PACKAGE
  FIELDS:
  - TITLE: UID
    TYPE: String
    REQUIRED: True
  - TITLE: SPDXID
    TYPE: String
    REQUIRED: True
  - TITLE: PRIMARY_PURPOSE
    TYPE: String
    REQUIRED: False
  - TITLE: TITLE
    TYPE: String
    REQUIRED: False
  - TITLE: STATEMENT
    TYPE: String
    REQUIRED: False
  - TITLE: SUMMARY
    TYPE: String
    REQUIRED: False
  RELATIONS:
  - TYPE: Child
    ROLE: CONTAINS
- TAG: SPDX_FILE
  FIELDS:
  - TITLE: UID
    TYPE: String
    REQUIRED: True
  - TITLE: SPDXID
    TYPE: String
    REQUIRED: True
  - TITLE: PRIMARY_PURPOSE
    TYPE: String
    REQUIRED: False
  - TITLE: SUMMARY
    TYPE: String
    REQUIRED: False
  - TITLE: TITLE
    TYPE: String
    REQUIRED: False
  - TITLE: STATEMENT
    TYPE: String
    REQUIRED: False
  RELATIONS:
  - TYPE: Child
    ROLE: CONTAINS
  - TYPE: File
- TAG: SPDX_SNIPPET
  FIELDS:
  - TITLE: UID
    TYPE: String
    REQUIRED: True
  - TITLE: SPDXID
    TYPE: String
    REQUIRED: True
  - TITLE: PRIMARY_PURPOSE
    TYPE: String
    REQUIRED: False
  - TITLE: SUMMARY
    TYPE: String
    REQUIRED: False
  - TITLE: TITLE
    TYPE: String
    REQUIRED: False
  - TITLE: STATEMENT
    TYPE: String
    REQUIRED: False
  RELATIONS:
  - TYPE: Parent
    ROLE: REQUIREMENT_FOR
  - TYPE: File

[SPDX_PACKAGE]
UID: SPDXRef-DOCUMENT
SPDXID: SPDXRef-DOCUMENT
TITLE: Requirements for Untitled Project
STATEMENT: >>>
SPDX Document for project Untitled Project
<<<

[SPDX_PACKAGE]
UID: SPDXRef-PACKAGE
SPDXID: SPDXRef-PACKAGE
PRIMARY_PURPOSE: BOM
TITLE: Requirements package
STATEMENT: >>>
SPDX Package for project Untitled Project
<<<
SUMMARY: >>>
SPDX Package for project Untitled Project
<<<

[[SECTION]]
TITLE: Files

[SPDX_FILE]
UID: SPDXRef-File-SDocDocument-StrictDoc_OSLC_RM_demo
SPDXID: SPDXRef-File-SDocDocument-StrictDoc_OSLC_RM_demo
PRIMARY_PURPOSE: DOCUMENTATION
SUMMARY: SDPX File for document StrictDoc OSLC RM demo
TITLE: hello.sdoc
RELATIONS:
- TYPE: File
  PATH: hello.sdoc
- TYPE: Child
  VALUE: SDOC-JAZZ-INTEGRATION
  ROLE: CONTAINS
- TYPE: Child
  VALUE: SDOC-JAZZ-ROOT-SERVICES
  ROLE: CONTAINS
- TYPE: Child
  VALUE: SDOC-JAZZ-SERVICE-PROVIDER
  ROLE: CONTAINS
- TYPE: Child
  VALUE: SDOC-JAZZ-INSTANCE-SHAPE
  ROLE: CONTAINS
- TYPE: Child
  VALUE: SDOC-JAZZ-QUERY-SHAPE
  ROLE: CONTAINS
- TYPE: Child
  VALUE: SDOC-JAZZ-OAUTH
  ROLE: CONTAINS
- TYPE: Child
  VALUE: SDOC-JAZZ-PUBLIC-URI
  ROLE: CONTAINS
- TYPE: Child
  VALUE: SDOC-JAZZ-RDF
  ROLE: CONTAINS
- TYPE: Child
  VALUE: SDOC-JAZZ-LINK-UPDATES
  ROLE: CONTAINS
- TYPE: Child
  VALUE: SDOC-JAZZ-RM-RELATIONS
  ROLE: CONTAINS
- TYPE: Child
  VALUE: SDOC-JAZZ-INVERSE-RELATIONS
  ROLE: CONTAINS
- TYPE: Child
  VALUE: SDOC-JAZZ-STABLE-LINKS
  ROLE: CONTAINS

[[/SECTION]]

[[SECTION]]
TITLE: Snippets

[SPDX_SNIPPET]
UID: SDOC-JAZZ-INTEGRATION
SPDXID: SDOC-JAZZ-INTEGRATION
PRIMARY_PURPOSE: DOCUMENTATION
SUMMARY: SPDX Snippet for requirement SDOC-JAZZ-INTEGRATION
TITLE: Requirement 'Jazz integration'
RELATIONS:
- TYPE: File
  PATH: hello.sdoc
  LINE_RANGE: 10, 13

[SPDX_SNIPPET]
UID: SDOC-JAZZ-ROOT-SERVICES
SPDXID: SDOC-JAZZ-ROOT-SERVICES
PRIMARY_PURPOSE: DOCUMENTATION
SUMMARY: SPDX Snippet for requirement SDOC-JAZZ-ROOT-SERVICES
TITLE: Requirement 'Root services discovery'
RELATIONS:
- TYPE: File
  PATH: hello.sdoc
  LINE_RANGE: 15, 22
- TYPE: Parent
  VALUE: SDOC-JAZZ-INTEGRATION
  ROLE: REQUIREMENT_FOR

[SPDX_SNIPPET]
UID: SDOC-JAZZ-SERVICE-PROVIDER
SPDXID: SDOC-JAZZ-SERVICE-PROVIDER
PRIMARY_PURPOSE: DOCUMENTATION
SUMMARY: SPDX Snippet for requirement SDOC-JAZZ-SERVICE-PROVIDER
TITLE: Requirement 'Service provider catalog'
RELATIONS:
- TYPE: File
  PATH: hello.sdoc
  LINE_RANGE: 24, 31
- TYPE: Parent
  VALUE: SDOC-JAZZ-INTEGRATION
  ROLE: REQUIREMENT_FOR

[SPDX_SNIPPET]
UID: SDOC-JAZZ-INSTANCE-SHAPE
SPDXID: SDOC-JAZZ-INSTANCE-SHAPE
PRIMARY_PURPOSE: DOCUMENTATION
SUMMARY: SPDX Snippet for requirement SDOC-JAZZ-INSTANCE-SHAPE
TITLE: Requirement 'Requirement instance shape'
RELATIONS:
- TYPE: File
  PATH: hello.sdoc
  LINE_RANGE: 33, 40
- TYPE: Parent
  VALUE: SDOC-JAZZ-INTEGRATION
  ROLE: REQUIREMENT_FOR

[SPDX_SNIPPET]
UID: SDOC-JAZZ-QUERY-SHAPE
SPDXID: SDOC-JAZZ-QUERY-SHAPE
PRIMARY_PURPOSE: DOCUMENTATION
SUMMARY: SPDX Snippet for requirement SDOC-JAZZ-QUERY-SHAPE
TITLE: Requirement 'Query capability resource shape'
RELATIONS:
- TYPE: File
  PATH: hello.sdoc
  LINE_RANGE: 42, 49
- TYPE: Parent
  VALUE: SDOC-JAZZ-INTEGRATION
  ROLE: REQUIREMENT_FOR

[SPDX_SNIPPET]
UID: SDOC-JAZZ-OAUTH
SPDXID: SDOC-JAZZ-OAUTH
PRIMARY_PURPOSE: DOCUMENTATION
SUMMARY: SPDX Snippet for requirement SDOC-JAZZ-OAUTH
TITLE: Requirement 'OAuth 1.0a discovery'
RELATIONS:
- TYPE: File
  PATH: hello.sdoc
  LINE_RANGE: 51, 58
- TYPE: Parent
  VALUE: SDOC-JAZZ-INTEGRATION
  ROLE: REQUIREMENT_FOR

[SPDX_SNIPPET]
UID: SDOC-JAZZ-PUBLIC-URI
SPDXID: SDOC-JAZZ-PUBLIC-URI
PRIMARY_PURPOSE: DOCUMENTATION
SUMMARY: SPDX Snippet for requirement SDOC-JAZZ-PUBLIC-URI
TITLE: Requirement 'Public resource identity'
RELATIONS:
- TYPE: File
  PATH: hello.sdoc
  LINE_RANGE: 60, 67
- TYPE: Parent
  VALUE: SDOC-JAZZ-INTEGRATION
  ROLE: REQUIREMENT_FOR

[SPDX_SNIPPET]
UID: SDOC-JAZZ-RDF
SPDXID: SDOC-JAZZ-RDF
PRIMARY_PURPOSE: DOCUMENTATION
SUMMARY: SPDX Snippet for requirement SDOC-JAZZ-RDF
TITLE: Requirement 'RDF representations'
RELATIONS:
- TYPE: File
  PATH: hello.sdoc
  LINE_RANGE: 69, 76
- TYPE: Parent
  VALUE: SDOC-JAZZ-INTEGRATION
  ROLE: REQUIREMENT_FOR

[SPDX_SNIPPET]
UID: SDOC-JAZZ-LINK-UPDATES
SPDXID: SDOC-JAZZ-LINK-UPDATES
PRIMARY_PURPOSE: DOCUMENTATION
SUMMARY: SPDX Snippet for requirement SDOC-JAZZ-LINK-UPDATES
TITLE: Requirement 'Writable link updates'
RELATIONS:
- TYPE: File
  PATH: hello.sdoc
  LINE_RANGE: 78, 85
- TYPE: Parent
  VALUE: SDOC-JAZZ-INTEGRATION
  ROLE: REQUIREMENT_FOR

[SPDX_SNIPPET]
UID: SDOC-JAZZ-RM-RELATIONS
SPDXID: SDOC-JAZZ-RM-RELATIONS
PRIMARY_PURPOSE: DOCUMENTATION
SUMMARY: SPDX Snippet for requirement SDOC-JAZZ-RM-RELATIONS
TITLE: Requirement 'OSLC RM relation mapping'
RELATIONS:
- TYPE: File
  PATH: hello.sdoc
  LINE_RANGE: 87, 94
- TYPE: Parent
  VALUE: SDOC-JAZZ-INTEGRATION
  ROLE: REQUIREMENT_FOR

[SPDX_SNIPPET]
UID: SDOC-JAZZ-INVERSE-RELATIONS
SPDXID: SDOC-JAZZ-INVERSE-RELATIONS
PRIMARY_PURPOSE: DOCUMENTATION
SUMMARY: SPDX Snippet for requirement SDOC-JAZZ-INVERSE-RELATIONS
TITLE: Requirement 'Inverse relation projection'
RELATIONS:
- TYPE: File
  PATH: hello.sdoc
  LINE_RANGE: 96, 103
- TYPE: Parent
  VALUE: SDOC-JAZZ-INTEGRATION
  ROLE: REQUIREMENT_FOR

[SPDX_SNIPPET]
UID: SDOC-JAZZ-STABLE-LINKS
SPDXID: SDOC-JAZZ-STABLE-LINKS
PRIMARY_PURPOSE: DOCUMENTATION
SUMMARY: SPDX Snippet for requirement SDOC-JAZZ-STABLE-LINKS
TITLE: Requirement 'Stable requirement links'
RELATIONS:
- TYPE: File
  PATH: hello.sdoc
  LINE_RANGE: 105, 112
- TYPE: Parent
  VALUE: SDOC-JAZZ-RM-RELATIONS
  ROLE: REQUIREMENT_FOR

[[/SECTION]]

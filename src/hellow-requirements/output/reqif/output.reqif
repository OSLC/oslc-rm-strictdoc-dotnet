# Documentation export by StrictDoc

# Specification: StrictDoc OSLC RM demo

## SDOC-JAZZ-INTEGRATION: Jazz integration
The StrictDoc OSLC RM server shall interoperate with Jazz as an OSLC RM 2.0 provider.

## SDOC-JAZZ-ROOT-SERVICES: Root services discovery
The server shall publish an RDF/XML OSLC root-services document that advertises the RM service-provider catalog and Jazz OSLC catalog descriptor.
- Decomposes -> SDOC-JAZZ-INTEGRATION

## SDOC-JAZZ-SERVICE-PROVIDER: Service provider catalog
The server shall expose an RM service-provider catalog that lists the StrictDoc document service providers and their RM domain.
- Decomposed by -> SDOC-JAZZ-INTEGRATION

## SDOC-JAZZ-INSTANCE-SHAPE: Requirement instance shape
Each requirement representation shall advertise a provider-owned OSLC RM instance shape that describes its writable link properties.
- Elaborates -> SDOC-JAZZ-INTEGRATION

## SDOC-JAZZ-QUERY-SHAPE: Query capability resource shape
The RM query capability shall advertise the same requirement resource shape that individual requirement representations use.
- Elaborated by -> SDOC-JAZZ-INTEGRATION

## SDOC-JAZZ-OAUTH: OAuth 1.0a discovery
Root services shall advertise OAuth 1.0a consumer registration, request-token, authorization, and access-token endpoints compatible with Jazz.
- Specifies -> SDOC-JAZZ-INTEGRATION

## SDOC-JAZZ-PUBLIC-URI: Public resource identity
Discovery, catalog, service-provider, dialog, shape, OAuth, and requirement links shall use the externally visible HTTPS origin.
- Specified by -> SDOC-JAZZ-INTEGRATION

## SDOC-JAZZ-RDF: RDF representations
The server shall serve OSLC resource representations through RDF content negotiation and include OSLC-Core-Version 2.0.
- Constrains -> SDOC-JAZZ-INTEGRATION

## SDOC-JAZZ-LINK-UPDATES: Writable link updates
The provider shall accept Jazz updates to provider-owned requirement links and return a response that Jazz recognizes as a successful save.
- Constrained by -> SDOC-JAZZ-INTEGRATION

## SDOC-JAZZ-RM-RELATIONS: OSLC RM relation mapping
The server shall map StrictDoc Decomposes, Elaborates, Specifies, Constrains, and Satisfies roles to their corresponding OSLC RM properties.
- Satisfies -> SDOC-JAZZ-INTEGRATION

## SDOC-JAZZ-INVERSE-RELATIONS: Inverse relation projection
The server shall add the OSLC RM inverse relation to target requirements when reading a StrictDoc JSON export.
- Satisfied by -> SDOC-JAZZ-INTEGRATION

## SDOC-JAZZ-STABLE-LINKS: Stable requirement links
Requirement relation targets shall use stable public requirement URIs so Jazz can navigate and retain links.
- Decomposes -> SDOC-JAZZ-RM-RELATIONS

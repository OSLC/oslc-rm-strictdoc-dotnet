# Documentation export by StrictDoc

# Specification: StrictDoc

## SDOC-HIGH-REQS-MANAGEMENT: Requirements management
StrictDoc shall enable requirements management.

## SDOC-HIGH-REQS-DECOMP: Requirements decomposition
StrictDoc shall support requirement decomposition.
- Parent -> SDOC-HIGH-REQS-MANAGEMENT
